TestModule DEFINITIONS EXPLICIT TAGS ::=
BEGIN
EXPORTS TestSeq, ListOfTestSeq;

--#org.lastrix.asn1s.SequenceOfTestClass#
TestSeq ::= [APPLICATION 2] IMPLICIT SEQUENCE {
  a INTEGER,
  b INTEGER,
  c REAL-Float,
  d UTF8String,
  myField TestSeqAsField
}

--#org.lastrix.asn1s.SequenceOfTestClassAsField#
TestSeqAsField ::= [APPLICATION 9] IMPLICIT SEQUENCE {
  id INTEGER,
  name UTF8String,
  weight REAL-Float
}

--#java.util.ArrayList#
ListOfTestSeq ::= [APPLICATION 12] SEQUENCE OF TestSeq
END
