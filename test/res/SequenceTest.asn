-- Test module, SHOULD NOT BE USED on non-clean schema --
-- DO NOT MODIFY IT UNLESS YOU KNOW WHAT YOU'RE DOING --
SequenceTest DEFINITIONS IMPLICIT TAGS ::=
BEGIN
EXPORTS ALL;

--#java.util.ArrayList#
TestSequenceOf ::= [APPLICATION 1] SEQUENCE OF INTEGER-Integer;

--#org.lastrix.asn1s.util.TestObject#
TestObject ::= [APPLICATION 2] SEQUENCE {
    id INTEGER-Integer,
    name UTF8String,
    weight REAL-Float
}
END
