TestModule { 1 2 111 } DEFINITIONS IMPLICIT TAGS ::=
BEGIN
EXPORTS ListOfTestSeq, TestSeq;
--#java.util.ArrayList#
ListOfTestSeq ::= [APPLICATION 12] SEQUENCE OF TestModule.TestSeq;
--#org.lastrix.asn1s.SequenceOfTestClass#
TestSeq ::= [APPLICATION 2] SEQUENCE {
      a INTEGER ( 0 | 10 .. 100  | 1000 .. 1100 ^ 1050 .. 1150),
      b INTEGER,
      c REAL-Float,
      d UTF8String,
      myField TestModule.TestSeqAsField
}
--#org.lastrix.asn1s.SequenceOfTestClassAsField#
TestSeqAsField ::= [APPLICATION 9] SEQUENCE {
      id INTEGER,
      name UTF8String,
      weight REAL-Float
}
END
